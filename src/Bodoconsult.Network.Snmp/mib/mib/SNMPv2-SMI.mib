-- SNMPv2-SMI.html
-- HTML generated by MG-SOFT MIB Explorer Version 2.0 Build 351
-- Monday, November 03, 2003 at 17:28:09

-- HTML group index:
-- RMON2-MIB, RFC1155-SMI, RFC1213-MIB, RMON-MIB, SNMPv2-SMI, 
-- SNMPv2-TC, TOKEN-RING-RMON-MIB.
--

SNMPv2-SMI DEFINITIONS ::= BEGIN

--
-- Node definitions
--
	-- 0
	ccitt OBJECT IDENTIFIER ::= { 0 }

	-- 0.0
	zeroDotZero OBJECT-IDENTITY
		STATUS current
		DESCRIPTION
			"A value used for null identifiers."
	::= { ccitt 0 }


	-- 1
	iso OBJECT IDENTIFIER ::= { 1 }

	-- 1.3
	org OBJECT IDENTIFIER ::= { iso 3 }

	-- 1.3.6
	dod OBJECT IDENTIFIER ::= { org 6 }

	-- 1.3.6.1
	internet OBJECT IDENTIFIER ::= { dod 1 }

	-- 1.3.6.1.1
	directory OBJECT IDENTIFIER ::= { internet 1 }

	-- 1.3.6.1.2
	mgmt OBJECT IDENTIFIER ::= { internet 2 }

	-- 1.3.6.1.2.1
	mib-2 OBJECT IDENTIFIER ::= { mgmt 1 }

	-- 1.3.6.1.2.1.10
	transmission OBJECT IDENTIFIER ::= { mib-2 10 }

	-- 1.3.6.1.3
	experimental OBJECT IDENTIFIER ::= { internet 3 }

	-- 1.3.6.1.4
	private OBJECT IDENTIFIER ::= { internet 4 }

	-- 1.3.6.1.4.1
	enterprises OBJECT IDENTIFIER ::= { private 1 }

	-- 1.3.6.1.5
	security OBJECT IDENTIFIER ::= { internet 5 }

	-- 1.3.6.1.6
	snmpV2 OBJECT IDENTIFIER ::= { internet 6 }

	-- 1.3.6.1.6.1
	snmpDomains OBJECT IDENTIFIER ::= { snmpV2 1 }

	-- 1.3.6.1.6.2
	snmpProxys OBJECT IDENTIFIER ::= { snmpV2 2 }

	-- 1.3.6.1.6.3
	snmpModules OBJECT IDENTIFIER ::= { snmpV2 3 }

END
